(defun c:by( / aa bb cc)

	ユーザーのCAD設定を記憶するパート

	*************************************************

	1　ユーザーに図形を選択させたり、数値を入力させたりする、情報収集パート

	2　AutoLISPが計算する、計算パート

	3　AutoLISPに何かを描かせたり、変更させる、作図パート

	*************************************************

	ユーザーのCAD設定を元に戻すパート
)
