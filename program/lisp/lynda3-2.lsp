(VL-LOAD-COM)
(DEFUN C:VLACADDOBJ (/ ACADOBJ) 
  (SETQ ACADOBJ (VLAX-GET-ACAD-OBJECT))
  (SETQ ACADPREFS (VLA-GET-PREFERENCES ACADOBJ))
  (SETQ ACADDISP (VLA-GET-DISPLAY ACADPREFS))
  ; カーソルサイズを変更する
  (VLA-PUT-CURSORSIZE ACADDISP 25)
  (SETVAR "CURSORSIZE" 5)
  (PRINC)
)
